package DETECT_Feedback {
    doc
    /* Where the web app's "Feedback" links send user feedback.
     * Edit these values to change the recipient or the attention line.
     */

    attribute feedback_email : ScalarValues::String = "osd-sea@mail.mil";
    attribute feedback_attention : ScalarValues::String = "Attn: DEM&S";
}
